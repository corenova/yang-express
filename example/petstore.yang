module petstore {
  prefix ps;
  namespace "urn:ietf:params:xml:ns:yang:example-petstore";
  description "Yang Petstore";
  grouping Pet {
    leaf id   { type uint64; mandatory true; }
    leaf name { type string; mandatory true; }
    leaf tag  { type string; }
  }
  list pet { key "id"; uses Pet; }
}
