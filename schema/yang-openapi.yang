module yang-openapi {
  namespace "urn:ietf:params:xml:ns:yang:yang-openapi";
  prefix openapi;
  yang-version 1.1;

  import ietf-inet-types { prefix inet; }
  import ietf-yang-types { prefix yang; }
  import yang-meta-types { prefix meta; }

  organization
    "Corenova Technologies, Inc.";
  contact
    "Peter K. Lee <peter@corenova.com>";
  reference
    "https://openapis.org";

  identity protocol {
    description "describes transfer protocol";
  }
  identity http {
    base protocol;
  }
  identity https {
    base protocol;
  }
  identity ws {
    base protocol;
  }
  identity wss {
    base protocol;
  }

  typedef json-schema-ref {
    type string {
      
    }
  }
  typedef mimetype {
    type string {
      pattern '^.+\/.+$';
    }
  }
  typedef http-status-code {
    type uint16 {
      range '100..102 | 200..208 | 226 | 300..308 | 400..431 | 500..511';
    }
  }
  grouping datatype {
    leaf type {
      type enumeration {
        enum string;
        enum number;
        enum integer;
        enum boolean;
        enum array;
        enum file;
        enum object;
      }
    }
    leaf format {
      type union {
        type enumeration {
          enum int32;
          enum int64;
          enum float;
          enum double;
          enum byte;
          enum binary;
          enum date;
          enum date-time;
          enum password;
        }
        type string;
      }
    }
  }
  grouping info {
    description
      "Contains metadata information to describe API.";
    leaf title       { type meta:title; mandatory true; }
    leaf description { type meta:description; }
    leaf version     { type meta:api-version; mandatory true; }
    container contact {
      leaf name { type meta:person-name; }
      leaf url { type inet:uri; }
      leaf email { type meta:email-address; }
    }
    container license {
      leaf name { type meta:license; mandatory true; }
      leaf url  { type inet:uri; }
    }
  }
  grouping json-schema {
    leaf $ref {
      type json-schema-ref;
    }
    uses openapi:datatype;
    leaf-list required {
      type leafref {
        path '../property/name';
      }
    }
    list property {
      key name;
      leaf name {
        type yang:yang-identifier;
      }
      uses openapi:json-schema {
        when "../name";
      }
    }
    list item {
      when "../type = 'array'";
      uses openapi:json-schema {
        when "../name";
      }
    }
  }
  grouping response {
    leaf description {
      type meta:description;
    }
    container schema {
      uses openapi:json-schema;
    }
    list header {
      
    }
    list example {
      
    }
  }
  grouping operation {
    leaf-list tags {
      type string;
    }
    leaf summary {
      type meta:description {
        length 0..120;
      }
    }
    leaf description {
      type meta:description;
    }
    leaf operationId {
      type string;
    }
    leaf-list consumes {
      type mimetype;
    }
    leaf-list produces {
      type mimetype;
    }
    leaf-list schemes {
      type identityref {
        base protocol;
      }
    }
    leaf deprecated {
      type boolean;
      default false;
    }
    list response {
      key code;
      leaf code {
        type http-status-code;
      }
      uses openapi:response;
    }
  }
  grouping specification {
    grouping path-item {
      leaf $ref {
        type json-schema-ref;
      }
      container get {
        uses operation;
      }
      container put {
        uses operation;
      }
      container post {
        uses operation;
      }
      container delete {
        uses operation;
      }
      container options {
        uses operation;
      }
      container head {
        uses operation;
      }
      container patch {
        uses operation;
      }
      list parameter {
        
      }
    }
    leaf swagger {
      type meta:api-version;
      default '2.0';
    }
    container info {
      uses openapi:info;
    }
    leaf host {
      type string;
    }
    leaf basePath {
      type inet:uri;
    }
    leaf-list schemes {
      type identityref {
        base protocol;
      }
    }
    leaf-list consumes {
      type mimetype;
      min-elements 1;
    }
    leaf-list produces {
      type mimetype;
      min-elements 1;
    }
    list path {
      key name;
      leaf name {
        type inet:uri;
      }
      uses path-item;
    }
    list definition {
      key name;
      leaf name {
        type yang:yang-identifier;
      }
      uses openapi:json-schema;
    }
    list response {
      key name;
      leaf name {
        type yang:yang-identifier;
      }
      uses openapi:response;
    }
  }

  rpc transform {
    input {
      uses specification;
    }
  }
}
