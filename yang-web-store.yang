module yang-web-store {
  namespace "urn:ietf:params:xml:ns:yang:yang-web-store";
  prefix web;
  yang-version 1.1;

  import ietf-inet-types { prefix inet; }
  import ietf-yang-library { prefix yanglib; }
  import yang-openapi { prefix openapi; }

  organization
    "Corenova Technologies, Inc.";
  contact
    "Peter K. Lee <peter@corenova.com>";
  description
    "This module provides YANG model-driven middleware routing";

  revision 2018-11-12 {
    description
      "Update to ES6.";
  }
  revision 2016-09-14 {
    description
      "Initial revision.";
  }
  
  /*
   * Features
   */
  feature express {
    description
      "Express.js web server framework capability.

       This feature component is the primary instance powering
       additional features provided by the yang-express module.

       It utilizes the Express.js web server framework to dynamically
       instanticate the web server and makes itself available for
       remote management.";
    reference "http://expressjs.com";
  }
  feature router {
    if-feature express;
  }
  feature body-parser {
    if-feature express;
  }
  feature multipart {
    if-feature express;
  }
  feature discover {
    if-feature router;
  }
  feature restjson {
    if-feature router;
    if-feature body-parser;
    if-feature multipart;
    description "YANG model-driven REST/JSON middleware router";
  }
  feature openapi {
    if-feature restjson;
    description "YANG model-driven openapi/swagger 2.0 spec generator";
  }
  feature os {
    description "Operating System runtime variables";
  }
  /*
   * Identities
   */
  identity router;
  identity restjson  { base router; }
  identity openapi   { base router; }
  /*
   * Groupings
   */
  /*
   * Configuration data nodes
   */
  container server {
    leaf port {
      type uint16;
      default 5000;
    }
    leaf hostname {
      if-feature os;
      type string;
      config false;
    }
    leaf-list modules {
      // hack for now
      type string;
      // type leafref {
      //   path '/yanglib:modules-state/module/name';
      // }
    }
    leaf-list routers {
      type identityref {
        base router;
      }
    }
  }
  /*
   * Remote Procedure Calls
   */
  rpc listen {
    if-feature express;
    description
      "Starts an instance of yang-express based on provided parameters.";
    input {
      anydata app {
        description
          "optional instance of express application";
      }
    }
    output {
      anydata instance;
    }
  }
}
